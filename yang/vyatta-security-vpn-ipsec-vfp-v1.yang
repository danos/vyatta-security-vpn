module vyatta-security-vpn-ipsec-vfp-v1 {
	namespace "urn:vyatta.com:mgmt:vyatta-security-vpn-ipsec-vfp:1";
	prefix vyatta-security-vpn-ipsec-vfp-v1;

	import vyatta-security-v1 {
		prefix security;
	}
	import vyatta-security-vpn-ipsec-v1 {
		prefix ipsec;
	}
	import vyatta-security-vpn-ipsec-remote-access-server-v1 {
		prefix server;
	}
	import vyatta-interfaces-v1 {
		prefix if;
	}
	import vyatta-interfaces-vfp-v1 {
		prefix if-vfp;
	}
	import configd-v1 {
		prefix configd;
	}

	organization "AT&T Inc.";
	contact
		"AT&T Inc.
		 Postal: 208 S. Akard Street
		         Dallas, TX 75202
		 Web: www.att.com";

	description
		"Copyright (c) 2017-2019, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-security-vpn-ipsec-vfp-v1";

	revision 2020-06-25 {
		description "Correct contact details";
	}

	revision 2019-07-16 {
		description "Added ipsec-ra-server-vfp feature to augment uses vfp to remote-access-server tunnel.";
	}

	revision 2018-01-11 {
		description "Augment uses vfp to remote-access-client tunnel.";
	}

	revision 2017-11-14 {
		description "Initial revision.";
	}

	feature ipsec-ra-server-vfp {
		description "Remote access server vfp configuration";
	}

	grouping uses-vfp {
		leaf uses {
			description "The virtual feature point to associate with the tunnel";
			configd:help "The virtual feature point to associate with the tunnel";
			type leafref {
				configd:pattern-help "<vfpN>";
				path "/if:interfaces/if-vfp:virtual-feature-point/if-vfp:ifname";
			}
		}
	}

	augment /security:security/ipsec:vpn/ipsec:ipsec/ipsec:site-to-site/ipsec:peer/ipsec:tunnel {
		uses uses-vfp;
	}

	augment /security:security/ipsec:vpn/ipsec:ipsec/ipsec:remote-access-client/ipsec:profile/ipsec:tunnel {
		uses uses-vfp;
	}

	augment /security:security/ipsec:vpn/ipsec:ipsec/server:remote-access-server/server:profile/server:tunnel {
		if-feature ipsec-ra-server-vfp;
		uses uses-vfp;
	}
}
