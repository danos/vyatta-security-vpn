module vyatta-security-vpn-ipsec-v1 {
	namespace "urn:vyatta.com:mgmt:vyatta-security-vpn-ipsec:1";
	prefix vyatta-security-vpn-ipsec-v1;

	import vyatta-security-v1 {
		prefix security;
	}
	import vyatta-types-v1 {
		prefix types;
	}
	import configd-v1 {
		prefix configd;
	}
	import vyatta-interfaces-v1 {
		prefix vyatta-if-v1;
	}

	organization "AT&T Inc.";
	contact
		"AT&T Inc.
		 Postal: 280 S. Akard Street
		         Dallas, TX 75202
		 Web: www.att.com";

	description
		"Copyright (c) 2017-2021 AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-security-vpn-ipsec-v1";

	revision 2021-07-28 {
		description "Increase maximum IKE worker-threads to 128";
	}
	revision 2020-06-25 {
		description "Correct contact details";
	}
	revision 2020-05-27 {
		description "Obsolete hash sha1_160";
	}
	revision 2020-04-07 {
		description "Call site-to-site stale-tunnel teardown hook only once";
	}
	revision 2019-11-19 {
		description "Deprecate optional compression as no longer implemented";
	}
	revision 2019-06-27 {
		description "IPsec RA client: support domains as server address.";
	}
	revision 2019-03-25 {
		description "IKE control-plane scaling parameters.
			     New log-modes minimal.
			     Add configd:must to improve efficiency of interface
			     leafref validation.";
	}
	revision 2018-09-26 {
		description "Add DMVPN feature.";
	}
	revision 2018-07-17 {
		description "IPsec RA client: Addition of CLI restrictions.
			     RA Client will only support DPD action: clear.
			     Ensure at a minimum esp-group, ike-group are
			     configured along with authentication parameters.";
	}
	revision 2018-07-02 {
		description "IPsec RA client: WAN failover support.
			     Logging for connection-manager/vyatta-ike-sa-daemon.
			     IPsec RA client: reconnect backoff timer.";
	}
	revision 2018-04-17 {
		description "Allow Suite-B/AES GCM configuration for IKE.";
	}
	revision 2018-03-09 {
		description "Add a feature toggle for configuring max_ikev1_exchanges.
			     Add X.509 certificate status configuration.";
	}
	revision 2018-01-23 {
		description "IPsec RA client: local identification configuration support.
			     IPsec RA client: Overlay VRF support.
			     Add new hierarchy for remote access client.
			     Add new hierarchy for global IKE configurations.";
	}
	revision 2017-02-13 {
		description "Rework YANG nodeset != comparison";
	}
	revision 2017-01-27 {
		description "DMVPN: Support DMVPN X.509 authentication.";
	}
	revision 2016-12-05 {
		description "Remove configd_end.sh in /security/vpn/ipsec/profile/bind/tunnel";
	}
	revision 2016-11-21 {
		description "DMVPN: Support individual local and remote IDs for authentication.";
	}

	revision 2016-10-24 {
		description "Support x509 CA certificates as list.";
	}
	revision 2016-04-12 {
		description
		 "site-to-site: support any as local-address value.
		  Introduce hash algorithm null, required for AES GCM encryptions.
		  Remove use of bash in action scripts.
		  Mark deprecated CLI: security vpn ipsec auto-update.";
	}
	revision 2015-12-04 {
		description "Use common grouping for pre-shared-key nodes.";
	}
	revision 2015-08-10 {
		description "Initial revision of version 1.";
	}

	feature x509-status {
		description "X.509 certificate status check configuration";
	}

	feature dmvpn-auth-x509 {
		description "DMVPN X.509 authentication";
	}

	feature ipsec_ra_client {
		description "Remote access client configuration";
	}

	feature global-ike-configuration {
		description "Global IKE configuration";
	}

	feature max-ikev1-exchanges {
		description "Max IKEv1 exchanges";
	}

	feature dmvpn {
		description "DMVPN support";
	}

	rpc clear-vpn-x509-status {
		description "Clear X.509 CRL and OCSP response cache of the IPsec VPN subsystem.";
	}

	grouping hash {
		leaf hash {
			type enumeration {
				enum "md5" {
					configd:help "MD5 HMAC";
				}
				enum "sha1" {
					configd:help "SHA1 HMAC (default)";
				}
				enum "sha1_160" {
					status obsolete;
					configd:help "SHA1_160 hash";
				}
				enum "sha2_256" {
					configd:help "SHA2_256_128 HMAC";
				}
				enum "sha2_384" {
					configd:help "SHA2_384_192 HMAC";
				}
				enum "sha2_512" {
					configd:help "SHA2_512_256 HMAC";
				}
				enum "null" {
					configd:help "no separate integrity function";
				}
			}
			configd:help "Hash algorithm";
			default "sha1";
			configd:validate "/opt/vyatta/share/tmplscripts/security/vpn/ipsec/esp-group-name/proposal/hash/configd_validate1.cli";
		}
	}

	grouping ike-group-name {
		leaf ike-group {
			type string;
			configd:help "Internet Key Exchange (IKE) group name [REQUIRED]";
			configd:allowed "echo $VAR(/security/vpn/ipsec/ike-group/@@)";
			configd:validate "/opt/vyatta/share/tmplscripts/security/vpn/ipsec/ike-group-name/configd_validate1.cli";
		}
	}

	grouping esp-group-name {
		leaf esp-group {
			type string;
			configd:help "ESP group name";
			configd:allowed	"echo $VAR(/security/vpn/ipsec/esp-group/@@)";
			configd:validate "/opt/vyatta/share/tmplscripts/security/vpn/ipsec/esp-group-name/configd_validate1.cli";
		}
	}

	grouping pre-shared-secret {
		leaf pre-shared-secret {
			description "Pre-shared secret key

				     Only the following characters are allowed to be used for setting
				     pre-shared secret key:

				     alphanumeric characters a-z A-Z 0-9
				     special characters      - + & ! @ # $ % ^ * ( ) , . : _

				     Example usage : 'aA1-&!@,.:_2Bb'";
			type string {
				pattern '[-\+&!@#$%\^\*\(\),\.:_a-zA-Z0-9]+' {
					configd:error-message "invalid pre-shared secret key \"$VAR(@)\"

Only these characters are allowed to be used for setting pre-shared secret key :
alphanumeric characters      a-z A-Z 0-9
special characters           - + & ! @ # $ % ^ * ( ) , . : _

Use of single quotes to set pre-shared secret key is recommended.
Example usage : 'aA1-&!@,.:_2Bb'
";
				}
			}
			configd:secret "true";
			configd:help "Pre-shared secret key";
		}
	}

	grouping backoff-params {
		description "Configures back off parameters.";
		configd:help "Back off parameters";
		leaf delay {
			description "Configures back off delay in seconds. The next action will be delayed by the
				configured value. If the base parameter is set with a value greater than 1, the
				delay will be exponentially increased by the configured base value.

				delay = (delay * base ^ (iteration - 1))

				If a jitter value is provided the delay formula is:

				delay = (delay * base ^ (iteration -1)) - random(0, delay * jitter/100)

				If upper-limit is defined, which is highly-recommended, the delay will never
				exceed the upper-limit:

				delay = min(delay, upper-limit)";
			configd:help "Back off delay in seconds";
			type uint32 {
				range 1..28800;
			}
			default 120;
		}
		leaf base {
			description "Enables exponential back off by configuring the exponential base using a
				float/decimal value.";
			configd:help "Exponential base for back off";
			type decimal64 {
				fraction-digits 1;
				range 1.0..4.0;
			}
		}
		leaf jitter {
			description "Jitter is recommended on a high number of remote-access client, to spread the
				load on remote-access server outage/maintenance window.";
			configd:help "Jitter percentage";
			type uint32 {
				range 0..100;
			}
			default 0;
		}
		leaf upper-limit {
			description "If exponential back off is enabled, via the base parameter, the upper-limit
				guarantees that the increasing back-off will never exceed that defined limit.";
			configd:help "Upper limit in seconds";
			type uint32 {
				range 1..28800;
			}
		}
	}

	grouping failover-mode {
		leaf mode {
			description  "Configures failover mode for the remote-access client profile.";
			configd:help "Failover mode";
			type enumeration {
				enum "sequential" {
					description "Configures sequential failover mode. Uses user-ordered next listed entry.";
					configd:help "Use sequential failover mode";
				}
				enum "disable" {
					description "Disables failover entirely. Uses first-listed server only.";
					configd:help "Disable failover";
				}
				enum "random-start" {
					description "Configures random-start failover-mode. Starts with random server,
						then runs through list sequentially.";
					configd:help "Use random-start failover mode";
				}
			}
			default "sequential";
		}
	}

	grouping loglevel-params {
		description "Configures log level parameter.";
		configd:help "Log level parameters";

		leaf level {
			description "Log level for a specific subsystem of the connection manager.
					Following log levels are available, ordered by priority:
					* emerg (highest)
					* alert
					* crit
					* err
					* warning
					* notice (default): suitable for production use in large scale deployments.
					* info
					* debug (lowest): very verbose, not recommended for production use.";
			configd:help "Log level value";
			type enumeration {
				enum "emerg" {
					description "Log messages with emergency priority only.";
					configd:help "Emergency logging";
				}
				enum "alert" {
					description "Log messages with alert priority or higher.";
					configd:help "Alert logging";
				}
				enum "crit" {
					description "Log messages with critical priority or higher.";
					configd:help "Critical logging";
				}
				enum "err" {
					description "Log messages with error priority or higher.";
					configd:help "Error logging";
				}
				enum "warning" {
					description "Log messages with warning priority or higher.";
					configd:help "Warning logging";
				}
				enum "notice" {
					description "Log messages with notice priority or higher.";
					configd:help "Notice logging";
				}
				enum "info" {
					description "Log messages with informational priority or higher.";
					configd:help "Informational logging";
				}
				enum "debug" {
					description "Log messages with debug priority or higher.";
					configd:help "Debug logging";
				}
			}
		}
	}

	typedef any-keyword {
		description "any keyword";
		type enumeration {
			enum "any" {
				description "any keyword for address";
				configd:help "any keyword for address";
			}
		}
	}

	typedef username-pwd-pattern {
		description "Username and Password string";
		type string {
			length 1..128;
			pattern '[-\+&!@#$%\^\*\(\),\.:_a-zA-Z0-9]+' {
				configd:error-message "invalid pattern \"$VAR(@)\"

				Only these characters are allowed
				alphanumeric characters a-z A-Z 0-9
				special characters      - + & ! @ # $ % ^ * ( ) , . : _

				Example usage : 'aA1-&!@,.:_2Bb'";
			}
		}
	}

	augment /security:security {
		container vpn {
			presence "true";
			configd:priority "900";
			configd:help "Virtual Private Network (VPN)";
			configd:end "/opt/vyatta/share/tmplscripts/security/vpn/configd_end.sh";
			container rsa-keys {
				presence "true";
				configd:help "RSA keys";
				list rsa-key-name {
					configd:help "Name of remote RSA key";
					key "tagnode";
					leaf tagnode {
						type string;
						configd:help "Name of remote RSA key";
					}
					leaf rsa-key {
						type string;
						configd:help "Remote RSA key";
					}
				}
				container local-key {
					presence "true";
					configd:help "Local RSA key";
					leaf file {
						type string {
							configd:syntax "/opt/vyatta/share/tmplscripts/security/vpn/rsa-keys/local-key/file/configd_syntax1.cli";
						}
						configd:help "Local RSA key file location";
						configd:validate "/opt/vyatta/share/tmplscripts/security/vpn/rsa-keys/local-key/file/configd_validate1.cli";
						default "/opt/vyatta/etc/config/ipsec.d/rsa-keys/localhost.key";
					}
				}
			}
			container ipsec {
				presence "true";
				configd:help "VPN IP security (IPsec) parameters";
				container logging {
					presence "true";
					configd:help "IPsec logging";
					leaf-list log-modes {
						type enumeration {
							enum "raw" {
								configd:help "Shows the raw data dumps in hex for IKE communication";
							}
							enum "crypt" {
								configd:help "Shows the low level encryption/decryption operations on packets";
							}
							enum "parsing" {
								configd:help "Shows the encryption/decryption operations on IKE messages";
							}
							enum "emitting" {
								configd:help "Shows the encryption/decryption operations on IKE messages";
							}
							enum "control" {
								configd:help "Shows the messages from configuration management, IPSec kernel interface and library";
							}
							enum "all" {
								configd:help "Enables all logging options";
							}
							enum "private" {
								configd:help "Shows the raw data dumps in hex for CHILD_SA/IPSec SA and IKE_SA/ISAKMP SA";
							}
							enum "minimal" {
								configd:help "Minimal logging which includes IKE/Child SA up/down logging and errors.";
							}
						}
						ordered-by "user";
						configd:help "Log mode";
					}
					container connection-manager {
						description "Configures log level for the connection manager and it's individual subsystems.
								If the loglevel for 'all' is set, this is used for subsystems which have no
								loglevel defined.

								* 'job': logs job/worker management
								* 'path-monitor': logs the activity of the path-monitor integration
								* 'connection': logs all activities related to IKE/CHILD SAs and connections in general
								* 'event': logs all incoming low-level events from the platform";
						configd:help "Connection manager logging parameters";
						container all {
							uses loglevel-params;
						}
						container job {
							uses loglevel-params;
						}
						container path-monitor {
							uses loglevel-params;
						}
						container connection {
							uses loglevel-params;
						}
						container event {
							uses loglevel-params;
						}
					}
				}
				leaf auto-update {
					type uint32 {
						range 30..65535;
					}
					configd:help "Set auto-update interval for IPsec daemon.";
					status deprecated;
				}
				leaf disable-uniqreqids {
					type empty;
					status deprecated;
				}
				container site-to-site {
					presence "true";
					configd:help "Site to site VPN";
					configd:begin "/opt/vyatta/share/tmplscripts/security/vpn/ipsec/site-to-site/configd_begin.pl";
					list peer {
						configd:help "VPN peer";
						configd:validate "/opt/vyatta/share/tmplscripts/security/vpn/ipsec/site-to-site/peer/configd_validate1.cli";
						key "tagnode";
						leaf tagnode {
							type string;
							configd:help "VPN peer";
						}
						container authentication {
							presence "true";
							configd:help "Peer authentication [REQUIRED]";
							leaf rsa-key-name {
								type string {
									pattern '[-_a-zA-Z0-9\.]+' {
										configd:error-message "invalid RSA key name \"$VAR(@)\"";
									}
								}
								configd:help "RSA key name";
								configd:validate "/opt/vyatta/share/tmplscripts/security/vpn/ipsec/site-to-site/peer/authentication/rsa-key-name/configd_validate1.cli";
							}
							uses pre-shared-secret;
							leaf remote-id {
								type string {
									pattern '[ -~]+' {
										configd:error-message "invalid ID \"$VAR(@)\"";
									}
								}
								configd:help "ID for remote authentication";
							}
							container x509 {
								presence "true";
								configd:help "X.509 certificate";
								leaf ca-cert-file {
									type string {
										configd:syntax "/opt/vyatta/share/tmplscripts/security/vpn/ipsec/site-to-site/peer/authentication/x509/ca-cert-file/configd_syntax1.cli";
									}
									configd:help "File containing the X.509 certificate for the Certificate Authority (CA)";
									status deprecated;
								}
								container key {
									presence "true";
									configd:help "Key file and password to open it";
									leaf password {
										type string;
										configd:secret "true";
										configd:help "Password that protects the private key";
									}
									leaf file {
										type string {
											configd:syntax "/opt/vyatta/share/tmplscripts/security/vpn/ipsec/site-to-site/peer/authentication/x509/key/file/configd_syntax1.cli";
										}
										configd:help "File containing the private key for the X.509 certificate for this host";
									}
								}
								leaf cert-file {
									type string {
										configd:syntax "/opt/vyatta/share/tmplscripts/security/vpn/ipsec/site-to-site/peer/authentication/x509/cert-file/configd_syntax1.cli";
									}
									configd:help "File containing the X.509 certificate for this host";
								}
								leaf crl-file {
									type string {
										configd:syntax "/opt/vyatta/share/tmplscripts/security/vpn/ipsec/site-to-site/peer/authentication/x509/crl-file/configd_syntax1.cli";
									}
									configd:help "File containing the X.509 Certificate Revocation List (CRL)";
								}
							}
							leaf mode {
								type enumeration {
									enum "pre-shared-secret" {
										configd:help "Use pre-shared secret key";
									}
									enum "x509" {
										configd:help "Use X.509 certificate";
									}
									enum "rsa" {
										configd:help "Use RSA key";
									}
								}
								configd:help "Authentication mode";
								configd:validate "/opt/vyatta/share/tmplscripts/security/vpn/ipsec/site-to-site/peer/authentication/mode/configd_validate1.cli";
								default "pre-shared-secret";
							}
							leaf id {
								type string {
									pattern '[ -~]+' {
										configd:error-message "invalid ID \"$VAR(@)\"";
									}
								}
								configd:help "ID for peer authentication";
							}
						}
						leaf description {
							type string;
							configd:help "VPN peer description";
						}
						list tunnel {
							configd:help "Peer tunnel [REQUIRED]";
							key "tagnode";
							leaf tagnode {
								type uint32;
								configd:help "Peer tunnel [REQUIRED]";
							}
							container local {
								presence "true";
								configd:help "Local parameters for interesting traffic";
								leaf prefix {
									type union {
										type types:ipv4-prefix;
										type types:ipv6-prefix;
									}
									configd:help "Local IPv4 or IPv6 prefix";
								}
								leaf port {
									type string;
									configd:help "Any TCP or UDP port";
								}
							}
							container remote {
								presence "true";
								configd:help "Remote parameters for interesting traffic";
								leaf prefix {
									type union {
										type types:ipv4-prefix;
										type types:ipv6-prefix;
									}
									configd:help "Remote IPv4 or IPv6 prefix";
								}
								leaf port {
									type string;
									configd:help "Any TCP or UDP port";
								}
							}
							leaf allow-public-networks {
								type enumeration {
									enum "enable";
									enum "disable";
								}
								configd:help "Option to allow public networks";
								default "disable";
								status deprecated;
							}
							leaf allow-nat-networks {
								type enumeration {
									enum "enable";
									enum "disable";
								}
								configd:help "Option to allow NAT networks";
								default "disable";
								status deprecated;
							}
							leaf disable {
								type empty;
								configd:help "Option to disable vpn tunnel";
							}
							uses esp-group-name;
							leaf protocol {
								type string {
									configd:syntax "/opt/vyatta/share/tmplscripts/security/vpn/ipsec/site-to-site/peer/tunnel/protocol/configd_syntax1.cli";
								}
								configd:help "Protocol to encrypt";
								configd:allowed "/opt/vyatta/share/tmplscripts/security/vpn/ipsec/site-to-site/peer/tunnel/protocol/configd_allowed.sh";
							}
						}
						leaf local-address {
							type string {
								configd:syntax "/opt/vyatta/share/tmplscripts/security/vpn/ipsec/site-to-site/peer/local-address/configd_syntax.sh";
							}
							configd:help "IPv4 or IPv6 address of a local interface to use for VPN";
							configd:allowed "/opt/vyatta/share/tmplscripts/security/vpn/ipsec/site-to-site/peer/local-address/configd_allowed.sh";
						}
						leaf dhcp-interface {
							type string;
							configd:help "DHCP interface to listen on";
							configd:allowed "/opt/vyatta/share/tmplscripts/security/vpn/ipsec/site-to-site/peer/dhcp-interface/configd_allowed.sh";
						}
						leaf default-esp-group {
							type string;
							configd:help "Default ESP group name";
							configd:allowed	"echo $VAR(/security/vpn/ipsec/esp-group/@@)";
							configd:validate "/opt/vyatta/share/tmplscripts/security/vpn/ipsec/site-to-site/peer/default-esp-group/configd_validate1.cli";
						}
						container vti {
							presence "true";
							configd:help "Virtual tunnel interface [REQUIRED]";
							uses esp-group-name;
							leaf bind {
								type string;
								configd:help "VTI tunnel interface associated with this configuration [REQUIRED]";
								configd:allowed "echo $VAR(/interfaces/vti/@@)";
								configd:validate "/opt/vyatta/share/tmplscripts/security/vpn/ipsec/site-to-site/peer/vti/bind/configd_validate1.cli";
							}
						}
						leaf connection-type {
							type enumeration {
								enum "initiate" {
									configd:help "This endpoint can initiate or respond to a connection";
								}
								enum "respond" {
									configd:help "This endpoint will only respond to a connection";
								}
							}
							configd:help "Connection type";
							default "initiate";
						}
						uses ike-group-name;
					}
				}
				container nat-networks {
					presence "true";
					configd:help "Network Address Translation (NAT) networks";
					list allowed-network {
						configd:help "NAT networks to allow";
						key "tagnode";
						leaf tagnode {
							type types:ipv4-prefix;
							configd:help "NAT networks to allow";
						}
						leaf-list exclude {
							type types:ipv4-prefix;
							ordered-by "user";
							configd:help "NAT networks to exclude from allowed-networks";
						}
					}
				}
				list profile {
					if-feature dmvpn;
					must "not(../remote-access-client)" {
						error-message "Cannot define ipsec profile configuration with remote-access-client";
					}
					configd:help "VPN IPSec Profile";
					key "tagnode";
					leaf tagnode {
						type string;
						configd:help "VPN IPSec Profile";
					}
					container authentication {
						presence "true";
						configd:help "Authentication [REQUIRED]";
						uses pre-shared-secret;
						leaf mode {
							type string {
								configd:syntax "/opt/vyatta/share/tmplscripts/security/vpn/ipsec/profile/authentication/mode/configd_syntax1.cli";
							}
							configd:help "Authentication mode";
							configd:validate "/opt/vyatta/share/tmplscripts/security/vpn/ipsec/profile/authentication/mode/configd_validate1.cli";
							default "pre-shared-secret";
						}
						leaf id {
							description "ID for peer authentication";
							type string {
								length 1..255;
							}
							configd:help "ID for peer authentication";
						}
						leaf remote-id {
							description "ID for remote authentication";
							type string {
								length 1..255;
							}
							configd:help "ID for remote authentication";
						}
						container x509 {
							presence "Use X.509 certificate";
							if-feature dmvpn-auth-x509;
							description "Configure X.509 authentication for this IPsec profile.";
							configd:help "X.509 certificate";
							container key {
								configd:help "Key file and password to open it";
								description "Configures the key file and password used for X.509 authentication";
								leaf password {
									description "Configures the password for the private key file for the X.509 Certificate used for authentication";
									type string {
										length 1..255;
									}
									configd:secret "true";
									configd:help "Password that protects the private key";
								}
								leaf file {
									description "Configures the private key file for the X.509 Certificate used for authentication";
									mandatory true;
									type string {
										configd:syntax "/opt/vyatta/share/tmplscripts/security/vpn/ipsec/site-to-site/peer/authentication/x509/key/file/configd_syntax1.cli";
										length 1..255;
									}
									configd:help "File containing the private key for the X.509 certificate for this host";
								}
							}
							leaf cert-file {
								description "Configures the X.509 Certificate for authentication";
								mandatory true;
								type string {
									configd:syntax "/opt/vyatta/share/tmplscripts/security/vpn/ipsec/site-to-site/peer/authentication/x509/cert-file/configd_syntax1.cli";
									length 1..255;
								}
								configd:help "File containing the X.509 certificate for this host";
							}
						}

					}
					uses esp-group-name {
						refine esp-group {
							configd:help "ESP group name [REQUIRED]";
						}
					}
					container bind {
						presence "true";
						configd:help "DMVPN crypto configuration";
						list tunnel {
							configd:help "Tunnel interface associated with this configuration profile";
							configd:allowed "/opt/vyatta/share/tmplscripts/security/vpn/ipsec/profile/bind/tunnel/configd_allowed.sh";
							configd:validate "/opt/vyatta/share/tmplscripts/security/vpn/ipsec/profile/bind/tunnel/configd_validate1.cli";
							key "tagnode";
							leaf tagnode {
								type string;
								configd:help "Tunnel interface associated with this configuration profile";
								configd:allowed "/opt/vyatta/share/tmplscripts/security/vpn/ipsec/profile/bind/tunnel/configd_allowed.sh";
							}
						}
					}
					uses ike-group-name;
				}
				leaf nat-traversal {
					type enumeration {
						enum "enable";
						enum "disable";
					}
					configd:help "Network Address Translation (NAT) traversal";
					status deprecated;
				}
				list esp-group {
					configd:help "Name of Encapsulating Security Payload (ESP) group";
					key "tagnode";
					leaf tagnode {
						type string {
							pattern '[-_a-zA-Z0-9\.]+' {
								configd:error-message "invalid ESP group name \"$VAR(@)\"";
							}
						}
						configd:help "Name of Encapsulating Security Payload (ESP) group";
					}
					list proposal {
						configd:help "ESP-group proposal [REQUIRED]";
						must "not(encryption = 'aes128gcm128' or encryption = 'aes256gcm128') or hash = 'null'" {
							error-message "No hash/integrity algorithm allowed for selected authenticated encryption algorithm";
						}
						must "not(encryption = 'aes128' or encryption = 'aes256' or encryption = '3des') or not(hash = 'null')" {
							error-message "Selected encryption algorithm cannot have null hash/integrity algorithm";
						}
						key "tagnode";
						leaf tagnode {
							type uint32 {
								range 1..65535;
							}
							configd:help "ESP-group proposal";
						}
						uses hash;
						leaf encryption {
							type enumeration {
								enum "aes128" {
									configd:help "AES-128 encryption (default)";
								}
								enum "aes256" {
									configd:help "AES-256 encryption";
								}
								enum "3des" {
									configd:help "3DES encryption";
								}
								enum "aes128gcm128" {
									configd:help "128 bit AES-GCM with 128 bit ICV";
								}
								enum "aes256gcm128" {
									configd:help "256 bit AES-GCM with 128 bit ICV";
								}
							}
							configd:help "Encryption algorithm";
							default "aes128";
						}
					}
					leaf compression {
						type enumeration {
							enum "enable" {
								configd:help "Enable ESP compression";
							}
							enum "disable" {
								configd:help "Disable ESP compression (default)";
							}
						}
						configd:help "ESP compression";
						default "disable";
						status deprecated;
					}
					leaf mode {
						type enumeration {
							enum "tunnel" {
								configd:help "Tunnel mode (default)";
							}
							enum "transport" {
								configd:help "Transport mode";
							}
						}
						configd:help "ESP mode";
						default "tunnel";
					}
					leaf lifetime {
						type uint32 {
							range 30..86400;
						}
						configd:help "ESP lifetime";
						default "3600";
					}
					leaf pfs {
						type enumeration {
							enum "enable" {
								configd:help "Enable PFS. Use ike-group's dh-group (default)";
							}
							enum "disable" {
								configd:help "Disable PFS";
							}
							enum "dh-group2" {
								configd:help "Enable PFS. Use Diffie-Hellman group 2";
							}
							enum "dh-group5" {
								configd:help "Enable PFS. Use Diffie-Hellman group 5";
							}
							enum "dh-group14" {
								configd:help "Enable PFS. Use Diffie-Hellman group 14";
							}
							enum "dh-group15" {
								configd:help "Enable PFS. Use Diffie-Hellman group 15";
							}
							enum "dh-group16" {
								configd:help "Enable PFS. Use Diffie-Hellman group 16";
							}
							enum "dh-group17" {
								configd:help "Enable PFS. Use Diffie-Hellman group 17";
							}
							enum "dh-group18" {
								configd:help "Enable PFS. Use Diffie-Hellman group 18";
							}
							enum "dh-group19" {
								configd:help "Enable PFS. Use Diffie-Hellman group 19";
							}
							enum "dh-group20" {
								configd:help "Enable PFS. Use Diffie-Hellman group 20";
							}
						}
						configd:help "ESP Perfect Forward Secrecy";
						default "enable";
					}
					leaf disable-strict-mode {
						type empty;
						configd:help "Disable strict-mode proposal negotiation for ESP.";
					}
				}
				list ike-group {
					configd:help "Name of Internet Key Exchange (IKE) group";
					key "tagnode";
					leaf tagnode {
						type string {
							pattern '[-_a-zA-Z0-9\.]+' {
								configd:error-message "invalid IKE group name \"$VAR(@)\"";
							}
						}
						configd:help "Name of Internet Key Exchange (IKE) group";
					}
					leaf ike-version {
						type enumeration {
							enum "1" {
								configd:help "Use IKEv1 keyexchange (default).";
							}
							enum "2" {
								configd:help "Use IKEv2 keyexchange.";
							}
							enum "2+1" {
								configd:help "Use IKEv2 keyexchange when initiating, but accept any protocol version when responding.";
							}
						}
						default "1";
						configd:help "IKE version for this proposal";
					}
					list proposal {
						configd:help "IKE-group proposal [REQUIRED]";
						must "not(encryption = 'aes128gcm128' or encryption = 'aes256gcm128') or (../ike-version = '2')" {
							error-message "IKEv1 not allowed for selected encryption algorithm";
						}
						must "not(encryption = 'aes128' or encryption = 'aes256' or encryption = '3des') or not(hash = 'null')" {
							error-message "Selected encryption algorithm cannot have null hash/integrity algorithm";
						}
						configd:validate "/opt/vyatta/share/tmplscripts/security/vpn/ipsec/ike-group-name/proposal/configd_validate1.cli";
						key "tagnode";
						leaf tagnode {
							type uint32 {
								range 1..65535;
							}
							configd:help "IKE-group proposal";
						}
						uses hash;
						leaf encryption {
							type enumeration {
								enum "aes128" {
									configd:help "AES-128 encryption (default)";
								}
								enum "aes256" {
									configd:help "AES-256 encryption";
								}
								enum "3des" {
									configd:help "3DES encryption";
								}
								enum "aes128gcm128" {
									configd:help "128 bit AES-GCM with 128 bit ICV";
								}
								enum "aes256gcm128" {
									configd:help "256 bit AES-GCM with 128 bit ICV";
								}
							}
							configd:help "Encryption algorithm";
							default "aes128";
						}
						leaf dh-group {
							type uint32 {
								configd:syntax "/opt/vyatta/share/tmplscripts/security/vpn/ipsec/ike-group/proposal/dh-group/configd_syntax1.cli";
							}
							configd:help "Diffie-Hellman (DH) key exchange group";
						}
					}
					container dead-peer-detection {
						presence "true";
						configd:help "Dead Peer Detection (DPD)";
						leaf action {
							type enumeration {
								enum "hold" {
									configd:help "Set action to hold (default)";
								}
								enum "clear" {
									configd:help "Set action to clear";
								}
								enum "restart" {
									configd:help "Set action to restart";
								}
							}
							configd:help "Keep-alive failure action";
							default "hold";
						}
						leaf interval {
							type uint32 {
								range 0..86400;
							}
							configd:help "Keep-alive interval";
							default "30";
						}
						leaf timeout {
							type uint32 {
								range 30..86400;
							}
							configd:help "Keep-alive timeout (IKEv1 only)";
							configd:validate "/opt/vyatta/share/tmplscripts/security/vpn/ipsec/ike-group/dead-peer-detection/timeout/configd_validate1.cli";
							default "120";
						}
					}
					leaf lifetime {
						type uint32 {
							range 30..86400;
						}
						configd:help "IKE lifetime";
						default "28800";
					}
					leaf disable-strict-mode {
						type empty;
						configd:help "Disable strict-mode proposal negotiation for IKE.";
					}
				}
				container remote-access-client {
					if-feature ipsec_ra_client;
					presence "IPsec remote access client configuration";
					must "not(../site-to-site)" {
						error-message "Cannot define remote-access-client with site-to-site";
					}
					description "Configures the remote access client parameters";
					configd:help "Remote access client VPN";
					list profile {
						description "Configures the profile for remote access client";
						configd:help "Remote access client VPN profile";
						min-elements 1;
						max-elements 8;
						key "profile-name";
						leaf profile-name {
							description "Configures profile name for remote access client";
							type string {
								length 1..255;
							}
							configd:help "Remote access client VPN profile";
						}
						container authentication {
							description "Configures authentication parameters for remote access client";
							configd:help "Authentication";
							must "not(mode = 'psk+eap-gtc') or (id/type and id/value)" {
								error-message "Authentication method psk+eap-gtc requires an id type and value to be set.";
							}
							uses pre-shared-secret;
							leaf mode {
								description "Configures the mode of authentication";
								type enumeration {
									enum "psk+eap-gtc" {
										description "Configures authentication mode as psk with eap-gtc";
										configd:help "Use psk+eap-gtc authentication";
									}
									enum "x509" {
										description "Configures authentication mode as X.509";
										configd:help "Use X.509 authentication";
									}
								}
								configd:help "Authentication mode";
								mandatory true;
							}
							leaf username {
								description "Configures username for authentication.

									Only the following characters are allowed
									alphanumeric characters a-z A-Z 0-9
									special characters      - + & ! @ # $ % ^ * ( ) , . : _

									Example usage : 'aA1-&!@,.:_2Bb'";
								type username-pwd-pattern;
								configd:help "Username for authentication";
							}
							leaf password {
								description "Configures password for authentication.

									Only the following characters are allowed
									alphanumeric characters a-z A-Z 0-9
									special characters      - + & ! @ # $ % ^ * ( ) , . : _

									Example usage : 'aA1-&!@,.:_2Bb'";
								type username-pwd-pattern;
								configd:secret "true";
								configd:help "Password for authentication";
							}
							container id {
								description "Configures identification for client authentication.";
								configd:help "Client identification";
								leaf value {
									description "Defines the identification value sent to the IPsec Remote-Access server
										during IKE authentication.";
									configd:help "Client identification value";
									type string {
										length 1..64;
									}
								}
								leaf type {
									description "Defines the identification type the identification value represents.";
									configd:help "Client identification type";
									type enumeration {
										enum "keyid" {
											description "Configures identification type ID_KEY_ID, which is an
												opaque octet stream to hold custom values.";
											configd:help "ID_KEY_ID / opaque octet stream";
										}
										enum "rfc822" {
											description "Configures identification type ID_RFC822_ADDR,
												which is a fully-qualified email address string.";
											configd:help "ID_RFC822_ADDR / email address";
										}
									}
								}
							}
							container x509 {
								presence "X.509 authentication parameters";
								configd:help "X.509 authentication parameters";
								description "Configuration X.509 certificate authentication parameters.";

								container key {
									presence "Private key parameters of the X.509 certificate";
									configd:help "Private key and password";
									description "Configuration X.509 private key parameters.
											Only if the private key is protected by a password,
											the private-key password needs to be given.";
									leaf password {
										type string;
										configd:secret "true";
										configd:help "Password that protects the private key";
										description "The password of a password protected X.509 private key.";
									}
									leaf file {
										type string {
											configd:syntax "/opt/vyatta/share/tmplscripts/security/vpn/ipsec/site-to-site/peer/authentication/x509/key/file/configd_syntax1.cli";
										}
										configd:help "Private key for the X.509 certificate for this client profile";
										description "Path of the private key for the X.509 certificate for this client profile.
											The private key must be located in /config/auth/ or in a sub-directory.";
									}
								}
								leaf cert-file {
									type string {
										configd:syntax "/opt/vyatta/share/tmplscripts/security/vpn/ipsec/site-to-site/peer/authentication/x509/cert-file/configd_syntax1.cli";
									}
									configd:help "X.509 certificate for this client profile";
									description "Path of the X.509 public certificate used for the
										authentication of this client profile.";
								}
							}

						}
						leaf description {
							description "Provides the description for remote access client profile";
							type string {
								length 1..255;
							}
							configd:help "Remote access client VPN profile description";
						}
						list server {
							description "Configures the list of remote-access servers for remote access client.
								The currently supported maximum are 12 servers.";
							configd:help "Remote-access servers";
							min-elements 1;
							max-elements 12;
							ordered-by "user";


							key "serveraddr";
							leaf serveraddr {
								type types:host;
								configd:help "Server address";
							}

							list source-interface {
								description "Configures the list of source-interfaces specific to the remote-access server address.
									The currently supported maximum are 4 source-interfaces.";
								configd:help "List of source-interfaces";
								configd:allowed "/opt/vyatta/sbin/vyatta-interfaces.pl --show all";
								max-elements 4;
								ordered-by "user";

								key "ifname";
								leaf ifname {
									description "Enables source-interface usage for specified remote-access server address";
									configd:help "Source-interface";
									type leafref {
										path "../../../source-interface/source-interface-ref";
									}
								}
							}
						}
						leaf install-vip-on {
							description "Specifies the interface where the virtual IP should be assigned";
							configd:help "Interface to install virtual IP on";
							configd:allowed "/opt/vyatta/sbin/vyatta-interfaces.pl --show all";
							type types:interface-ifname;
							must "(/vyatta-if-v1:interfaces/*/*[(local-name(.) = 'tagnode') or " +
								"(local-name(.) = 'ifname')] = current())" +
								"or /vyatta-if-v1:interfaces/*/*[local-name(.) = 'vif']" +
								"[./../* = substring-before(current(), '.')]" +
								"/*[(local-name(.) = 'tagnode') or " +
								"   (local-name(.) = 'ifname')]" +
								"[. = substring-after(current(), '.')]" {
								error-message "Interface must exist in the configuration";
								configd:must "is-interface-leafref-original(.)";
							}
						}
						list tunnel {
							description "Configures the list of tunnel for remote access client";
							min-elements 1;
							max-elements 32;
							configd:help "Remote tunnel";
							key "tunnel-id";
							leaf tunnel-id {
								description "Configures the id of tunnel";
								type uint32;
								configd:help "Remote tunnel id";
							}
							container local {
								description "Configures local parameters for the tunnel";
								configd:help "Local parameters for interesting traffic";
								leaf network {
									description "Configures local network for the tunnel";
									type union {
										type types:ipv4-prefix;
										type types:ipv6-prefix;
									}
									configd:help "Local IPv4 or IPv6 network";
								}
							}
							container remote {
								description "Configures remote parameters for the tunnel";
								configd:help "Remote parameters for interesting traffic";
								leaf network {
									description "Configures remote network for the tunnel";
									type union {
										type types:ipv4-prefix;
										type types:ipv6-prefix;
									}
									configd:help "Remote IPv4 or IPv6 network";
								}
							}
						}
						leaf local-address {
							description "Configures local address for remote access client";
							type union {
								type types:ipv4-address;
								type types:ipv6-address;
								type any-keyword;
							}
							configd:help "IPv4, IPv6 or any address of a local interface to use for remote access VPN";
						}
						uses esp-group-name {
							refine esp-group {
								mandatory true;
							}
						}
						uses ike-group-name {
							refine ike-group {
								must "/security:security/vpn/ipsec/ike-group[tagnode = current()]" +
								     "/dead-peer-detection/action = 'clear'" {
									error-message "Only 'clear' DPD action is supported for IPSec Remote-access client";
								}
								mandatory true;
							}
						}

						list source-interface {
							description "Configures list of source-interfaces for the remote-access client.
								The currently supported maximum are 4 source interfaces.";
							configd:help "List of source-interfaces";
							configd:allowed "/opt/vyatta/sbin/vyatta-interfaces.pl --show all";
							max-elements 4;

							key "source-interface-ref";
							leaf source-interface-ref {
								description "Configures the source-interfaces";
								configd:help "Source-interface";
								type types:interface-ifname;
								must "(/vyatta-if-v1:interfaces/*/*[(local-name(.) = 'tagnode') or " +
									"(local-name(.) = 'ifname')] = current())" +
									"or /vyatta-if-v1:interfaces/*/*[local-name(.) = 'vif']" +
									"[./../* = substring-before(current(), '.')]" +
									"/*[(local-name(.) = 'tagnode') or " +
									"   (local-name(.) = 'ifname')]" +
									"[. = substring-after(current(), '.')]" {
									error-message "Interface must exist in the configuration";
									configd:must "is-interface-leafref-original(.)";
								}
								must "not(/*[local-name(.) = 'routing']" +
									"/*[local-name(.) = 'routing-instance']" +
									"/*[local-name(.) = 'interface']" +
									"/*[local-name(.) = 'name'][. = current()])" {
									error-message "Interface must not be configured in a routing instance";
								}
								must "not(../../local-address)" {
									error-message "Cannot define source-interface and local-address at the same time";
								}
							}
							leaf priority {
								description "Configures source-interface priority.
									Priority range: 1 (highest) ... 1024 (lowest).";
								configd:help "Source-interface priority";
								type uint32 {
									range 1..1024;
								}
							}
						}

						container failover {
							description "Configures failover parameters for remote-access client profile.";
							configd:help "Failover parameters";
							uses failover-mode;
						}
						container backoff {
							description "Configures back off parameters for remote-access client profile.";
							configd:help "Back off parameters";
							container source-interfaces {
								uses backoff-params;
							}
							container servers {
								uses backoff-params;
							}
							container auth-failure {
								uses backoff-params;
							}
							container reconnect {
								uses backoff-params;
							}
						}
					}
				}
			}
			container x509 {
				description "Configures X.509 certificates which can be Root CA, sub CA,
							 or the Issuer CA for the X.509 authentication in IPsec.";
				configd:help "X.509 certificates";
				leaf-list ca-certs {
					description "Configures a list of X.509 Certificate Authority certificates";
					type string {
						configd:syntax "/opt/vyatta/share/tmplscripts/security/vpn/x509/configd_syntax1.cli";
					}
					configd:help "X.509 certificates for the Certificate Authority (CA)";
				}
				container status {
					if-feature x509-status;
					description "Configures X.509 certificate status / revocation global check behavior.";
					configd:help "X.509 certificate status check behavior (OCSP, CRL, ...)";
					leaf interface {
						description "Configures the interface to use for perform certificate status check.";
						configd:help "Interface to use for OCSP, CRL, ...";
						type types:interface-ifname;
						must "(/vyatta-if-v1:interfaces/*/*[(local-name(.) = 'tagnode') or " +
							"(local-name(.) = 'ifname')] = current())" +
							"or /vyatta-if-v1:interfaces/*/*[local-name(.) = 'vif']" +
							"[./../* = substring-before(current(), '.')]" +
							"/*[(local-name(.) = 'tagnode') or " +
							"   (local-name(.) = 'ifname')]" +
							"[. = substring-after(current(), '.')]" {
							error-message "Interface must exist in the configuration";
							configd:must "is-interface-leafref-original(.)";
						}
					}
					container crl {
						description "Configuration of Certification Revocation List check.";
						configd:help "CRL check behavior";
						leaf disable {
							type empty;
							description "Disables Certificate Revocation List checks entirely.";
							configd:help "Option to disable CRL check";
						}
						leaf cache {
							type empty;
							description "Cache CRLs from remote.";
							configd:help "Enable CRL cache";
						}
					}
					container ocsp {
						description "Configuration of Online Certificate Status Protocol (OCSP) check.";
						configd:help "OCSP check behavior";
						leaf disable {
							type empty;
							description "Disables Online Certificate Status Protocol (OCSP) checks entirely.";
							configd:help "Option to disable OCSP check";
						}
					}
				}
			}
			container ike {
				if-feature global-ike-configuration;
				description "Global Internet Key Exchange (IKE) configurations which affect all IKE based services.";
				configd:help "Global IKE configuration";
				leaf block-threshold {
					description "Configures the maximum number of half-open IKE SAs per peer IP address.

						     Sets the maximum number of simultaneously ongoing connection attempts ('half-open' IKE SAs)
						     for an individual peer IP address. If this threshold is exceeded by an individual IP address
						     the IKE_SA_INIT packets gets dropped by the IKE control-plane, no IKE error response is sent.";
					configd:help "Maximum number of half-open IKE SAs per peer address";
					type uint32 {
						range 0..max;
					}
					default 5;
				}
				leaf cookie-threshold {
					description "Configures the number of half-open IKE SAs which will enable the IKEv2 cookie generation.
						     To mitigate DDoS from many different peer addresses, IKEv2 is able to enable a cookie
						     mechanism, if the number of ongoing connection attempts ('half-open' IKE SAs), of all peers,
						     exceeds the cookie threshold.

						     The IKE control-plane will respond with a IKE_SA_INIT message, including a Cookie payload.
						     The peer needs to resend the exact same IKE_SA_INIT message as initially, including the
						     returned Cookie payload. This proofs that the request is not send from a forge source address
						     and that the peer is actually able to receive and process IKE messages.

						     Each cookie payload is unique. The cookie includes a randomly generated secret, which will
						     be reused for up to 10000 and then regenerated. The individually generated cookies have a
						     lifetime of 10 seconds.

						     If a peer sends an old cookie (cookie lifetime expired, old cookie secret), the IKE
						     control-plane will handle this as no cookie was provided and responses as if this would be
						     the first IKE_SA_INIT request from the peer.

						     There is a cookie mechanism calm down period of 10 seconds, which will keep the cookie
						     mechanism for 10 seconds since the last generated cookie. This means there needs to be a
						     period of 10 seconds of no new  connection attempts, to get the cookie mechanism turned off
						     again.

						     Cookie calm down period, cookie secret reuse limit, cookie secret length and cookie lifetime
						     are fixed parameters, not configurable.";
					configd:help "Threshold of half-open IKE SAs to enable the cookie mechanism (IKEv2)";
					type uint32 {
						range 0..max;
					}
					default 10;
				}

				leaf half-open-timeout {
					description "Configures the timeout of an ongoing IKE SA connection attempt in seconds.";
					configd:help "Half-open IKE SA timeout in seconds";
					type uint32 {
						range 15..60;
					}
					default 30;
				}
				leaf ikesa-limit {
					description "Configures the maximum number of simultaneous established IKE SAs.";
					configd:help "Maximum number of IKE SAs";
					type uint32 {
						range 10..max;
					}
				}
				leaf ikesa-table-size {
					description "Configures the hash table size to store IKE SAs.

						     Each hash table entry holds a linked-list used to store the IKE SAs.
						     By default the hash table size is one and only holds one linked-list, which
						     results in one single linked-list holding all IKE SAs. This is acceptable
						     for small setups with a small amount of IKE SAs installed.

						     Setups with many IKE SAs can partition the linked-list by creating multiple
						     linked-list. This is done by enhancing the hash table size. The key of the
						     hash table are based on the IKE SPIs.

						     During the hash table look a lock of the hash table is held. The
						     ikesa-table-segments option can be used to divide the table in
						     segments, so only partially segments get locked.

						     The value should be a power of two, otherwise it gets rounded to the next
						     higher of power of two.";
					configd:help "IKE SA hash table size";
					type uint32 {
						range 1..4096;
					}
					default 1;
				}
				leaf ikesa-table-segments {
					description "Configures the (lock) segments of the hash table to store IKE SAs.

						     The IKE SA hash table gets divided in multiple segments, which
						     then gets individually locked during a lookup or manipulation.

						     The value should be a power of two, otherwise it gets rounded to the next
						     higher of power of two.";
					configd:help "IKE SA hash table segments";
					type uint32 {
						range 1..4096;
					}
					default 1;
				}
				leaf init-limit-half-open {
					description "Configures the upper limit of half open IKE SAs. Exceeding this limit will result in
						     drops of incoming IKE SA INIT requests.";
					configd:help "Maximum number of half-open IKE SAs";
					type uint32 {
						range 10..max;
					}
				}
				leaf-list interface {
					description "Configures list of interfaces which should be used by the IKE control-plane.
						All other interfaces are ignored.";
					configd:help "List of interfaces";
					configd:allowed "/opt/vyatta/sbin/vyatta-interfaces.pl --show all";

					type types:interface-ifname;
					must "(/vyatta-if-v1:interfaces/*/*[(local-name(.) = 'tagnode') or " +
						"(local-name(.) = 'ifname')] = current())" +
						"or /vyatta-if-v1:interfaces/*/*[local-name(.) = 'vif']" +
						"[./../* = substring-before(current(), '.')]" +
						"/*[(local-name(.) = 'tagnode') or " +
						"   (local-name(.) = 'ifname')]" +
						"[. = substring-after(current(), '.')]" {
						configd:must "is-interface-leafref-original(.)";
						error-message "Interface must exist in the configuration";
					}
					must "not(/*[local-name(.) = 'routing']" +
						"/*[local-name(.) = 'routing-instance']" +
						"/*[local-name(.) = 'interface']" +
						"/*[local-name(.) = 'name'][. = current()])" {
						error-message "Interface must not be configured in a routing instance";
					}
				}
				leaf make-before-break {
					configd:help "Enable make-before-break re-authentication";
					description "By default re-authentication in IKEv2 is performed in a break-before-make way.
						     The make-before-break option allows to re-authenticate by establishing overlapping
						     IKE SAs. This is not supported by all IKE implementations and might cause
						     interoperability issues.

						     IKEv2 specific option.";
					type empty;
				}
				container retransmit {
					description "Configures retransmission of IKE protocol messages.
						     The formula of the retransmission for each attempt (n):

						     Relative retransmission timeout = timeout * base ^ (n - 1)

						     Example with default values: tries 5, timeout 4.0, base 1.8

						     #1 retransmission (n=1) after: 4.0 * 1.8 ^ (1 - 1) = 4.0s
						     #2 retransmission (n=2) after: 4.0 * 1.8 ^ (2 - 1) = 7.2s
						     #3 retransmission (n=3) after: 4.0 * 1.8 ^ (3 - 1) = 12.96s
						     #4 retransmission (n=4) after: 4.0 * 1.8 ^ (4 - 1) = 23.328s
						     #5 retransmission (n=5) after: 4.0 * 1.8 ^ (5 - 1) = 41.99040s
						     Last retransmission times out : 4.0 * 1.8 ^ (6 - 1) = 75.582720s

						     Retransmission configuration changes will have no impact on existing IKE SA.
						     Manual reset of IKE SA required instead.";



					configd:help "Parameters for IKE retransmission";
					leaf tries {
						description "Configures the number of attempts to deliver a protocol message.";
						configd:help "Number of tries";
						type uint32 {
							range 1..32;
						}
						default 5;
					}
					leaf timeout {
						description "Configures the timeout of a transmission in seconds.";
						configd:help "Transmission timeout in seconds";
						type decimal64 {
							fraction-digits 1;
							range 1.0..32.0;
						}
						default 4.0;
					}
					leaf base {
						description "Configures exponential base for delaying further retransmit attempts.";
						configd:help "Base of exponential retransmission delays";
						type decimal64 {
							fraction-digits 1;
							range 1.0..4.0;
						}
						default 1.8;
					}
				}
				leaf worker-threads {
					description "Configures the number of IKE control-plane worker threads.";
					configd:help "Number of worker threads";
					type uint32 {
						range 10..128;
					}
					default 16;
				}
				container v1 {
					configd:help "Global IKEv1 configuration parameters";
					description "Global IKEv1 configurations which affect all IKEv1 based services.";
					leaf max_ikev1_exchanges {
						type uint32 {
							range 3..1000;
						}
						configd:help "Maximum IKEv1 exchanges per IKE SA";
						description "Configures the maximum number of Quick Mode (QM) states that are cached for a given IKEv1 SA.";
						default "32";
						if-feature max-ikev1-exchanges;
					}
				}
			}

		}
	}
}
